module _3gpp-nr-nrm-nrcelldu {
  yang-version 1.1;
  namespace "urn:3gpp:sa5:_3gpp-nr-nrm-nrcelldu";
  prefix nrcelldu3gpp;

  import _3gpp-common-top { prefix top3gpp; }
  import _3gpp-common-managed-element { prefix me3gpp; }
  import _3gpp-nr-nrm-gnbdufunction { prefix gnbdu3gpp; }

  organization "3GPP SA5";
  description "3GPP TS 28.541 NRCellDU NRM used by NES and MRO playbooks over O1.";

  revision 2026-10-01 {
    description "Rel-18 baseline.";
  }

  augment "/me3gpp:ManagedElement/gnbdu3gpp:GNBDUFunction" {
    list NRCellDU {
      key "id";
      uses top3gpp:Top_Grp;
      container attributes {
        leaf administrativeState {
          type enumeration {
            enum LOCKED;
            enum UNLOCKED;
            enum SHUTTING_DOWN;
          }
          default UNLOCKED;
        }
        leaf cellIndividualOffset {
          type int32 { range "-24..24"; }
          units "dB";
          default 0;
        }
        leaf ssbPowerOffset {
          type int32 { range "-6..6"; }
          units "dB";
          default 0;
        }
        leaf nRPCI {
          type uint16 { range "0..1007"; }
        }
      }
    }
  }
}
