module _3gpp-nr-nrm-nrcellrelation {
  yang-version 1.1;
  namespace "urn:3gpp:sa5:_3gpp-nr-nrm-nrcellrelation";
  prefix nrcellrel3gpp;

  import _3gpp-common-top { prefix top3gpp; }
  import _3gpp-common-managed-element { prefix me3gpp; }
  import _3gpp-nr-nrm-gnbcucpfunction { prefix gnbcucp3gpp; }

  organization "3GPP SA5";
  description "3GPP TS 28.541 NRCellRelation NRM used by MRO and NES playbooks over O1.";

  revision 2026-10-01 {
    description "Rel-18 baseline.";
  }

  augment "/me3gpp:ManagedElement/gnbcucp3gpp:GNBCUCPFunction" {
    list NRCellRelation {
      key "id";
      uses top3gpp:Top_Grp;
      container attributes {
        leaf adjacentNRCellRef { type string; }
        leaf cellIndividualOffset {
          type int32 { range "-24..24"; }
          units "dB";
          default 0;
        }
        leaf a3Offset {
          type int32 { range "-30..30"; }
          units "half-dB";
          default 0;
        }
        leaf timeToTrigger {
          type uint16 { range "0..5120"; }
          units "ms";
          default 320;
        }
        leaf isHoAllowed {
          type boolean;
          default true;
        }
      }
    }
  }
}
