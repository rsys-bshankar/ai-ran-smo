module _3gpp-common-managed-element {
  yang-version 1.1;
  namespace "urn:3gpp:sa5:_3gpp-common-managed-element";
  prefix me3gpp;

  import _3gpp-common-top { prefix top3gpp; }

  organization "3GPP SA5";
  description "3GPP TS 28.622 ManagedElement NRM definition.";

  revision 2026-10-01 {
    description "Rel-18 baseline.";
  }

  list ManagedElement {
    key "id";
    uses top3gpp:Top_Grp;
    container attributes {
      leaf userLabel { type string; }
      leaf vendorName { type string; }
      leaf swVersion { type string; }
    }
  }
}
