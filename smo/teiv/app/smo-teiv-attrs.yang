module smo-teiv-attrs {
    yang-version 1.1;
    namespace "urn:smo:teiv:attrs";
    prefix teiv-attrs;

    import o-ran-smo-teiv-common-yang-types { prefix or-teiv-types; }
    import o-ran-smo-teiv-common-yang-extensions { prefix or-teiv-yext; }

    organization "SMO TE&IV";
    description
        "TE&IV's TS 28.541 / TS 28.622 attributes that smo-teiv's model has no column for, as decorators (O-RAN TE&IV-DM R005 v06.00 Annex E), loaded
        with createUserDefinedSchema at TE&IV's start (plan task S3.21). Generated by teiv/app/attrs.py from the classes' TS 28.541 schemas; do not
        edit. Every leaf is a string: a value outside a safe set of characters is 'j:' and the base64url of its JSON (attrs.py).";

    revision "2026-11-01" {
        description "The attributes of the classes TE&IV holds (S3.21).";
        or-teiv-yext:label 1.0.0;
    }

    augment /or-teiv-types:decorators {
        // The attributes per class:
        //   CCOFunction: CCOPilotPollutionParameters, CCOWeakCoverageParameters
        //   CESManagementFunction: esNotAllowedTimePeriod, interRatEsActivationCandidateCellParameters, interRatEsActivationOriginalCellParameters, interRatEsDeactivationCandidateCellParameters, intraRatEsActivationCandidateCellsLoadParameters, intraRatEsDeactivationCandidateCellsLoadParameters
        //   DESManagementFunction: aIMLInferenceFunctionRefList, esNotAllowedTimePeriod, interRatEsActivationCandidateCellParameters, interRatEsActivationOriginalCellParameters, interRatEsDeactivationCandidateCellParameters, intraRatEsActivationCandidateCellsLoadParameters, intraRatEsDeactivationCandidateCellsLoadParameters, mLModelRefList
        //   DLBOFunction: aIMLInferenceFunctionRefList, mLModelRefList, maximumDeviationHoTrigger
        //   DMROFunction: aIMLInferenceFunctionRefList, mLModelRefList
        //   GNBCUCPFunction: configurable5QISetRef, dCHOControl, dDAPSHOControl, dynamic5QISetRef, ephemerisInfoSetRef, isOnboardSatellite, mWABRef, mappedCellIdInfoList, mappingSetIDBackhaulAddressList, mdtUserConsentReqList, nRECMappingRuleRef, onboardSatelliteId, peeParametersList, plmnId, priorityLabel, qceIdMappingInfoList, supportedPerfMetricGroups, supportedTraceMetrics, tceIDMappingInfoList, userLabel, vnfParametersList, x2AllowList, x2BlockList, x2HOBlockList, xnAllowList, xnBlockList, xnHOBlockList
        //   GNBDUFunction: configurable5QISetRef, dynamic5QISetRef, gnbDuName, iABRef, isOnboardSatellite, onboardSatelliteId, peeParametersList, priorityLabel, rimRSReportConf, supportedPerfMetricGroups, supportedTraceMetrics, userLabel, vnfParametersList
        //   ManagedElement: dnPrefix, locationName, managedBy, managedElementTypeList, priorityLabel, supportedPerfMetricGroups, supportedTraceMetrics, swVersion, userDefinedState, userLabel, vendorName
        //   NRCellCU: nRFrequencyRef, peeParametersList, plmnInfoList, priorityLabel, supportedPerfMetricGroups, supportedTraceMetrics, userLabel, vnfParametersList
        //   NRCellDU: administrativeState, aggressorSetRef, arfcnDL, arfcnSUL, arfcnUL, bSChannelBwDL, bSChannelBwSUL, bSChannelBwUL, bWPRef, bWPSetRef, cellState, nPNIdentityList, nRFrequencyRef, nTNTAClist, operationalState, peeParametersList, plmnInfoInfoList, priorityLabel, redCapAccessCriteriaRef, rimRSMonitoringOccasionInterval, rimRSMonitoringOccasionStartingOffset, rimRSMonitoringStartTime, rimRSMonitoringStopTime, rimRSMonitoringWindowDuration, rimRSMonitoringWindowPeriodicity, rimRSMonitoringWindowStartingOffset, ssbDuration, ssbFrequency, ssbOffset, ssbPeriodicity, ssbSubCarrierSpacing, supportedPerfMetricGroups, supportedTraceMetrics, uECellBarredAccess, userLabel, victimSetRef, vnfParametersList
        //   NRFreqRelation: CellReselectionRedcap, blockListEntry, blockListEntryIdleMode, cellReselectionSubPriority, nRFrequencyRef, qQualMin, tReselectionNRSfHigh, tReselectionNRSfMedium, threshXHighP, threshXHighQ, threshXLowP, threshXLowQ
        //   NRSectorCarrier: bSChannelBwUL, configuredMaxTxPower, peeParametersList, priorityLabel, sectorEquipmentFunctionRef, supportedPerfMetricGroups, supportedTraceMetrics, txDirection, userLabel, vnfParametersList
        //   SubNetwork: supportedPerfMetricGroups, supportedTraceMetrics
        leaf CCOPilotPollutionParameters { type string; }
        leaf CCOWeakCoverageParameters { type string; }
        leaf CellReselectionRedcap { type string; }
        leaf aIMLInferenceFunctionRefList { type string; }
        leaf administrativeState { type string; }
        leaf aggressorSetRef { type string; }
        leaf arfcnDL { type string; }
        leaf arfcnSUL { type string; }
        leaf arfcnUL { type string; }
        leaf bSChannelBwDL { type string; }
        leaf bSChannelBwSUL { type string; }
        leaf bSChannelBwUL { type string; }
        leaf bWPRef { type string; }
        leaf bWPSetRef { type string; }
        leaf blockListEntry { type string; }
        leaf blockListEntryIdleMode { type string; }
        leaf cellReselectionSubPriority { type string; }
        leaf cellState { type string; }
        leaf configurable5QISetRef { type string; }
        leaf configuredMaxTxPower { type string; }
        leaf dCHOControl { type string; }
        leaf dDAPSHOControl { type string; }
        leaf dnPrefix { type string; }
        leaf dynamic5QISetRef { type string; }
        leaf ephemerisInfoSetRef { type string; }
        leaf esNotAllowedTimePeriod { type string; }
        leaf gnbDuName { type string; }
        leaf iABRef { type string; }
        leaf interRatEsActivationCandidateCellParameters { type string; }
        leaf interRatEsActivationOriginalCellParameters { type string; }
        leaf interRatEsDeactivationCandidateCellParameters { type string; }
        leaf intraRatEsActivationCandidateCellsLoadParameters { type string; }
        leaf intraRatEsDeactivationCandidateCellsLoadParameters { type string; }
        leaf isOnboardSatellite { type string; }
        leaf locationName { type string; }
        leaf mLModelRefList { type string; }
        leaf mWABRef { type string; }
        leaf managedBy { type string; }
        leaf managedElementTypeList { type string; }
        leaf mappedCellIdInfoList { type string; }
        leaf mappingSetIDBackhaulAddressList { type string; }
        leaf maximumDeviationHoTrigger { type string; }
        leaf mdtUserConsentReqList { type string; }
        leaf nPNIdentityList { type string; }
        leaf nRECMappingRuleRef { type string; }
        leaf nRFrequencyRef { type string; }
        leaf nTNTAClist { type string; }
        leaf onboardSatelliteId { type string; }
        leaf operationalState { type string; }
        leaf peeParametersList { type string; }
        leaf plmnId { type string; }
        leaf plmnInfoInfoList { type string; }
        leaf plmnInfoList { type string; }
        leaf priorityLabel { type string; }
        leaf qQualMin { type string; }
        leaf qceIdMappingInfoList { type string; }
        leaf redCapAccessCriteriaRef { type string; }
        leaf rimRSMonitoringOccasionInterval { type string; }
        leaf rimRSMonitoringOccasionStartingOffset { type string; }
        leaf rimRSMonitoringStartTime { type string; }
        leaf rimRSMonitoringStopTime { type string; }
        leaf rimRSMonitoringWindowDuration { type string; }
        leaf rimRSMonitoringWindowPeriodicity { type string; }
        leaf rimRSMonitoringWindowStartingOffset { type string; }
        leaf rimRSReportConf { type string; }
        leaf sectorEquipmentFunctionRef { type string; }
        leaf ssbDuration { type string; }
        leaf ssbFrequency { type string; }
        leaf ssbOffset { type string; }
        leaf ssbPeriodicity { type string; }
        leaf ssbSubCarrierSpacing { type string; }
        leaf supportedPerfMetricGroups { type string; }
        leaf supportedTraceMetrics { type string; }
        leaf swVersion { type string; }
        leaf tReselectionNRSfHigh { type string; }
        leaf tReselectionNRSfMedium { type string; }
        leaf tceIDMappingInfoList { type string; }
        leaf threshXHighP { type string; }
        leaf threshXHighQ { type string; }
        leaf threshXLowP { type string; }
        leaf threshXLowQ { type string; }
        leaf txDirection { type string; }
        leaf uECellBarredAccess { type string; }
        leaf userDefinedState { type string; }
        leaf userLabel { type string; }
        leaf vendorName { type string; }
        leaf victimSetRef { type string; }
        leaf vnfParametersList { type string; }
        leaf x2AllowList { type string; }
        leaf x2BlockList { type string; }
        leaf x2HOBlockList { type string; }
        leaf xnAllowList { type string; }
        leaf xnBlockList { type string; }
        leaf xnHOBlockList { type string; }
    }
}
